module ietf-wson-topology {
  yang-version 1.1;
  namespace "urn:ietf:params:xml:ns:yang:ietf-wson-topology";
  prefix wsont;

  import ietf-network {
    prefix nw;
    reference
      "RFC 8345: A YANG Data Model for Network Topologies";
  }

  import ietf-network-topology {
    prefix nt;
    reference
      "RFC 8345: A YANG Data Model for Network Topologies";
  }

  import ietf-te-topology {
    prefix tet;
    reference
      "RFC 8795: YANG Data Model for
       Traffic Engineering (TE) Topologies";
  }

  import ietf-layer0-types {
    prefix l0-types;
    reference
      "RFC 9093: A YANG Data Model for Layer 0 Types";
  }

  organization
    "IETF CCAMP Working Group";

  contact
    "WG Web: <https://datatracker.ietf.org/wg/ccamp/>
     WG List: <mailto:ccamp@ietf.org>

     Editor:   Haomian Zheng  <zhenghaomian@huawei.com>
     Editor:   Young Lee  <younglee.tx@gmail.com>
     Editor:   Aihua Guo  <aihuaguo.ietf@gmail.com>
     Editor:   Victor Lopez <victor.lopez@nokia.com>
     Editor:   Daniel King  <d.king@lancaster.ac.uk>";

  description
    "This module provides a YANG data model for the routing and
     wavelength assignment (RWA) Traffic Engineering (TE)
     topology in Wavelength Switched Optical Networks (WSONs).
     The YANG data model described in this document is a WSON
     technology-specific YANG data model augmenting the generic TE
     topology module (ietf-te-topology) based on the information
     model developed in RFC 7446 and the two encoding documents
     RFC 7579 and RFC 7581.

     Copyright (c) 2021 IETF Trust and the persons identified
     as authors of the code.  All rights reserved.

     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC 9094; see
     the RFC itself for full legal notices.";

  revision 2021-07-19 {
    description
      "Initial version";

    reference
      "RFC 9094: A YANG Data Model for Wavelength Switched
       Optical Networks (WSONs)";
  }

  /*
   * Data nodes
   */

  augment "/nw:networks/nw:network/nw:network-types"
        + "/tet:te-topology" {
    description
      "Augment network types to define the WSON topology type.";
    container wson-topology {
      presence "Its presence identifies the WSON topology type.";
      description
        "Introduce a new network type for WSON topology.";
    }
  }

  augment "/nw:networks/nw:network/nw:node/tet:te"
        + "/tet:te-node-attributes" {
    when '/nw:networks/nw:network/nw:network-types'
       + '/tet:te-topology/wsont:wson-topology' {
      description
        "Augmentation parameters apply only for networks with
         WSON topology type.";
    }
    description
      "Augment TE node attributes.";
    container wson-node {
      presence "The TE node is a WSON node.";
      description
        "WSON node attributes";
      leaf is-reconfigurable-node {
        type boolean;
        default "true";
        description
          "Indicates whether the WSON node is reconfigurable:
           - true: the node is reconfigurable, i.e.,
             it is representing a Reconfigurable Optical
             Add/Drop Multiplexer (ROADM) node;
           - false: the node is not reconfigurable, i.e.,
             it is representing a Fixed Optical Add/Drop
             Multiplexer (FOADM) node.";
      }
    }
  }

  /*
   * Augment TE label range information
   */

  augment "/nw:networks/nw:network/nw:node/tet:te/"
        + "tet:te-node-attributes/tet:connectivity-matrices/"
        + "tet:label-restrictions/tet:label-restriction" {
    when '../../../../../../nw:network-types/tet:te-topology/'
       + 'wsont:wson-topology' {
      description
        "Augmentation parameters apply only for networks with
         WSON topology type.";
    }
    description
      "Augment TE label range information for the TE node
       connectivity matrices.";
    uses l0-types:l0-label-range-info;
  }

  augment "/nw:networks/nw:network/nw:node/tet:te/"
        + "tet:te-node-attributes/tet:connectivity-matrices/"
        + "tet:connectivity-matrix/tet:from/"
        + "tet:label-restrictions/tet:label-restriction" {
    when '../../../../../../../../nw:network-types/tet:te-topology/'
       + 'wsont:wson-topology' {
      description
        "Augmentation parameters apply only for networks with
         WSON topology type.";
    }
    description
      "Augment TE label range information for the source LTP
       of the connectivity matrix entry.";
    uses l0-types:l0-label-range-info;
  }

  augment "/nw:networks/nw:network/nw:node/tet:te/"
        + "tet:te-node-attributes/tet:connectivity-matrices/"
        + "tet:connectivity-matrix/tet:to/"
        + "tet:label-restrictions/tet:label-restriction" {
    when '../../../../../../../../nw:network-types/tet:te-topology/'
       + 'wsont:wson-topology' {
      description
        "Augmentation parameters apply only for networks with
         WSON topology type.";
    }
    description
      "Augment TE label range information for the destination LTP
       of the connectivity matrix entry.";
    uses l0-types:l0-label-range-info;
  }

  augment "/nw:networks/nw:network/nw:node/tet:te/"
        + "tet:information-source-entry/"
        + "tet:connectivity-matrices/tet:label-restrictions/"
        + "tet:label-restriction" {
    when '../../../../../../nw:network-types/tet:te-topology/'
       + 'wsont:wson-topology' {
      description
        "Augmentation parameters apply only for networks with
         WSON topology type.";
    }
    description
      "Augment TE label range information for the TE node
       connectivity matrices information source.";
    uses l0-types:l0-label-range-info;
  }

  augment "/nw:networks/nw:network/nw:node/tet:te/"
        + "tet:information-source-entry/tet:connectivity-matrices/"
        + "tet:connectivity-matrix/"
        + "tet:from/tet:label-restrictions/tet:label-restriction" {
    when '../../../../../../../../nw:network-types/tet:te-topology/'
       + 'wsont:wson-topology' {
      description
        "Augmentation parameters apply only for networks with
         WSON topology type.";
    }
    description
      "Augment TE label range information for the source LTP
       of the connectivity matrix entry information source.";
    uses l0-types:l0-label-range-info;
  }

  augment "/nw:networks/nw:network/nw:node/tet:te/"
        + "tet:information-source-entry/tet:connectivity-matrices/"
        + "tet:connectivity-matrix/"
        + "tet:to/tet:label-restrictions/tet:label-restriction" {
    when '../../../../../../../../nw:network-types/tet:te-topology/'
       + 'wsont:wson-topology' {
      description
        "Augmentation parameters apply only for networks with
         WSON topology type.";
    }
    description
      "Augment TE label range information for the destination LTP
       of the connectivity matrix entry information source.";
    uses l0-types:l0-label-range-info;
  }

  augment "/nw:networks/nw:network/nw:node/tet:te/"
        + "tet:tunnel-termination-point/"
        + "tet:local-link-connectivities/"
        + "tet:label-restrictions/tet:label-restriction" {
    when '../../../../../../nw:network-types/tet:te-topology/'
       + 'wsont:wson-topology' {
      description
        "Augmentation parameters apply only for networks with
         WSON topology type.";
    }
    description
      "Augment TE label range information for the Tunnel
       Termination Point (TTP) Local Link Connectivities.";
    uses l0-types:l0-label-range-info;
  }

  augment "/nw:networks/nw:network/nw:node/tet:te/"
        + "tet:tunnel-termination-point/"
        + "tet:local-link-connectivities/"
        + "tet:local-link-connectivity/"
        + "tet:label-restrictions/tet:label-restriction" {
    when '../../../../../../../nw:network-types/tet:te-topology/'
       + 'wsont:wson-topology' {
      description
        "Augmentation parameters apply only for networks with
         WSON topology type.";
    }
    description
      "Augment TE label range information for the TTP
       Local Link Connectivity entry.";
    uses l0-types:l0-label-range-info;
  }

  augment "/nw:networks/nw:network/nt:link/tet:te/"
        + "tet:te-link-attributes/"
        + "tet:label-restrictions/tet:label-restriction" {
    when '../../../../../nw:network-types/tet:te-topology/'
       + 'wsont:wson-topology' {
      description
        "Augmentation parameters apply only for networks with
         WSON topology type.";
    }
    description
      "Augment TE label range information for the TE link.";
    uses l0-types:l0-label-range-info;
  }

  augment "/nw:networks/nw:network/nt:link/tet:te/"
        + "tet:information-source-entry/"
        + "tet:label-restrictions/tet:label-restriction" {
    when '../../../../../nw:network-types/tet:te-topology/'
       + 'wsont:wson-topology' {
      description
        "Augmentation parameters apply only for networks with
         WSON topology type.";
    }
    description
      "Augment TE label range information for the TE link
       information source.";
    uses l0-types:l0-label-range-info;
  }

  augment "/nw:networks/tet:te/tet:templates/"
        + "tet:link-template/tet:te-link-attributes/"
        + "tet:label-restrictions/tet:label-restriction" {
    description
      "Augment TE label range information for the TE link template.";
    uses l0-types:l0-label-range-info;
  }

  /*
   * Augment TE label
   */

  augment "/nw:networks/nw:network/nw:node/tet:te/"
        + "tet:te-node-attributes/tet:connectivity-matrices/"
        + "tet:label-restrictions/tet:label-restriction/"
        + "tet:label-start/"
        + "tet:te-label/tet:technology" {
    when '../../../../../../../../nw:network-types/tet:te-topology/'
       + 'wsont:wson-topology' {
      description
        "Augmentation parameters apply only for networks with
         WSON topology type.";
    }
    description
      "Augment TE label range start for the TE node
       connectivity matrices.";
    case wson {
      uses l0-types:wson-label-start-end;
    }
  }

  augment "/nw:networks/nw:network/nw:node/tet:te/"
        + "tet:te-node-attributes/tet:connectivity-matrices/"
        + "tet:label-restrictions/"
        + "tet:label-restriction/tet:label-end/"
        + "tet:te-label/tet:technology" {
    when '../../../../../../../../nw:network-types/tet:te-topology/'
       + 'wsont:wson-topology' {
      description
        "Augmentation parameters apply only for networks with
         WSON topology type.";
    }
    description
      "Augment TE label range end for the TE node
       connectivity matrices.";
    case wson {
      uses l0-types:wson-label-start-end;
    }
  }

  augment "/nw:networks/nw:network/nw:node/tet:te/"
        + "tet:te-node-attributes/tet:connectivity-matrices/"
        + "tet:label-restrictions/"
        + "tet:label-restriction/tet:label-step/"
        + "tet:technology" {
    when '../../../../../../../nw:network-types/tet:te-topology/'
       + 'wsont:wson-topology' {
      description
        "Augmentation parameters apply only for networks with
         WSON topology type.";
    }
    description
      "Augment TE label range step for the TE node
       connectivity matrices.";
    case wson {
      uses l0-types:wson-label-step;
    }
  }

  augment "/nw:networks/nw:network/nw:node/tet:te/"
        + "tet:te-node-attributes/tet:connectivity-matrices/"
        + "tet:underlay/tet:primary-path/tet:path-element/"
        + "tet:type/tet:label/tet:label-hop/"
        + "tet:te-label/tet:technology" {
    when '../../../../../../../../../'
       + 'nw:network-types/tet:te-topology/'
       + 'wsont:wson-topology' {
      description
        "Augmentation parameters apply only for networks with
         WSON topology type.";
    }
    description
      "Augment TE label hop for the underlay primary path of the
       TE node connectivity matrices.";
    case wson {
      uses l0-types:wson-label-hop;
    }
  }

  augment "/nw:networks/nw:network/nw:node/tet:te/"
        + "tet:te-node-attributes/tet:connectivity-matrices/"
        + "tet:underlay/tet:backup-path/tet:path-element/"
        + "tet:type/tet:label/tet:label-hop/"
        + "tet:te-label/tet:technology" {
    when '../../../../../../../../../'
       + 'nw:network-types/tet:te-topology/'
       + 'wsont:wson-topology' {
      description
        "Augmentation parameters apply only for networks with
         WSON topology type.";
    }
    description
      "Augment TE label hop for the underlay backup path of the
       TE node connectivity matrices.";
    case wson {
      uses l0-types:wson-label-hop;
    }
  }

  augment "/nw:networks/nw:network/nw:node/tet:te/"
        + "tet:te-node-attributes/tet:connectivity-matrices/"
        + "tet:optimizations/tet:algorithm/tet:metric/"
        + "tet:optimization-metric/"
        + "tet:explicit-route-exclude-objects/"
        + "tet:route-object-exclude-object/"
        + "tet:type/tet:label/tet:label-hop/"
        + "tet:te-label/tet:technology" {
    when '../../../../../../../../../../'
       + 'nw:network-types/tet:te-topology/'
       + 'wsont:wson-topology' {
      description
        "Augmentation parameters apply only for networks with
         WSON topology type.";
    }
    description
      "Augment TE label hop for the explicit route objects excluded
       by the path computation of the TE node connectivity
       matrices.";
    case wson {
      uses l0-types:wson-label-hop;
    }
  }

  augment "/nw:networks/nw:network/nw:node/tet:te/"
        + "tet:te-node-attributes/tet:connectivity-matrices/"
        + "tet:optimizations/tet:algorithm/tet:metric/"
        + "tet:optimization-metric/"
        + "tet:explicit-route-include-objects/"
        + "tet:route-object-include-object/"
        + "tet:type/tet:label/tet:label-hop/"
        + "tet:te-label/tet:technology" {
    when '../../../../../../../../../../'
       + 'nw:network-types/tet:te-topology/'
       + 'wsont:wson-topology' {
      description
        "Augmentation parameters apply only for networks with
         WSON topology type.";
    }
    description
      "Augment TE label hop for the explicit route objects included
       by the path computation of the TE node connectivity
       matrices.";
    case wson {
      uses l0-types:wson-label-hop;
    }
  }

  augment "/nw:networks/nw:network/nw:node/tet:te/"
        + "tet:te-node-attributes/tet:connectivity-matrices/"
        + "tet:path-properties/tet:path-route-objects/"
        + "tet:path-route-object/tet:type/tet:label/tet:label-hop/"
        + "tet:te-label/tet:technology" {
    when '../../../../../../../../../'
       + 'nw:network-types/tet:te-topology/'
       + 'wsont:wson-topology' {
      description
        "Augmentation parameters apply only for networks with
         WSON topology type.";
    }
    description
      "Augment TE label hop for the computed path route objects
       of the TE node connectivity matrices.";
    case wson {
      uses l0-types:wson-label-hop;
    }
  }

  augment "/nw:networks/nw:network/nw:node/tet:te/"
        + "tet:te-node-attributes/tet:connectivity-matrices/"
        + "tet:connectivity-matrix/tet:from/"
        + "tet:label-restrictions/tet:label-restriction/"
        + "tet:label-start/"
        + "tet:te-label/tet:technology" {
    when '../../../../../../../../../../'
       + 'nw:network-types/tet:te-topology/'
       + 'wsont:wson-topology' {
      description
        "Augmentation parameters apply only for networks with
         WSON topology type.";
    }
    description
      "Augment TE label range start for the source LTP
       of the connectivity matrix entry.";
    case wson {
      uses l0-types:wson-label-start-end;
    }
  }

  augment "/nw:networks/nw:network/nw:node/tet:te/"
        + "tet:te-node-attributes/tet:connectivity-matrices/"
        + "tet:connectivity-matrix/tet:from/"
        + "tet:label-restrictions/tet:label-restriction/"
        + "tet:label-end/"
        + "tet:te-label/tet:technology" {
    when '../../../../../../../../../../'
       + 'nw:network-types/tet:te-topology/'
       + 'wsont:wson-topology' {
      description
        "Augmentation parameters apply only for networks with
         WSON topology type.";
    }
    description
      "Augment TE label range end for the source LTP
       of the connectivity matrix entry.";
    case wson {
      uses l0-types:wson-label-start-end;
    }
  }

  augment "/nw:networks/nw:network/nw:node/tet:te/"
        + "tet:te-node-attributes/tet:connectivity-matrices/"
        + "tet:connectivity-matrix/tet:from/"
        + "tet:label-restrictions/tet:label-restriction/"
        + "tet:label-step/"
        + "tet:technology" {
    when '../../../../../../../../../'
       + 'nw:network-types/tet:te-topology/'
       + 'wsont:wson-topology' {
      description
        "Augmentation parameters apply only for networks with
         WSON topology type.";
    }
    description
      "Augment TE label range step for the source LTP
       of the connectivity matrix entry.";
    case wson {
      uses l0-types:wson-label-step;
    }
  }

  augment "/nw:networks/nw:network/nw:node/tet:te/"
        + "tet:te-node-attributes/tet:connectivity-matrices/"
        + "tet:connectivity-matrix/tet:to/"
        + "tet:label-restrictions/tet:label-restriction/"
        + "tet:label-start/"
        + "tet:te-label/tet:technology" {
    when '../../../../../../../../../../'
       + 'nw:network-types/tet:te-topology/'
       + 'wsont:wson-topology' {
      description
        "Augmentation parameters apply only for networks with
         WSON topology type.";
    }
    description
      "Augment TE label range start for the destination LTP
       of the connectivity matrix entry.";
    case wson {
      uses l0-types:wson-label-start-end;
    }
  }

  augment "/nw:networks/nw:network/nw:node/tet:te/"
        + "tet:te-node-attributes/tet:connectivity-matrices/"
        + "tet:connectivity-matrix/tet:to/"
        + "tet:label-restrictions/tet:label-restriction/"
        + "tet:label-end/"
        + "tet:te-label/tet:technology" {
    when '../../../../../../../../../../'
       + 'nw:network-types/tet:te-topology/'
       + 'wsont:wson-topology' {
      description
        "Augmentation parameters apply only for networks with
         WSON topology type.";
    }
    description
      "Augment TE label range end for the destination LTP
       of the connectivity matrix entry.";
    case wson {
      uses l0-types:wson-label-start-end;
    }
  }

  augment "/nw:networks/nw:network/nw:node/tet:te/"
        + "tet:te-node-attributes/tet:connectivity-matrices/"
        + "tet:connectivity-matrix/tet:to/"
        + "tet:label-restrictions/tet:label-restriction/"
        + "tet:label-step/"
        + "tet:technology" {
    when '../../../../../../../../../'
       + 'nw:network-types/tet:te-topology/'
       + 'wsont:wson-topology' {
      description
        "Augmentation parameters apply only for networks with
         WSON topology type.";
    }
    description
      "Augment TE label range step for the destination LTP
       of the connectivity matrix entry.";
    case wson {
      uses l0-types:wson-label-step;
    }
  }

  augment "/nw:networks/nw:network/nw:node/tet:te/"
        + "tet:te-node-attributes/tet:connectivity-matrices/"
        + "tet:connectivity-matrix/"
        + "tet:underlay/tet:primary-path/tet:path-element/"
        + "tet:type/tet:label/tet:label-hop/"
        + "tet:te-label/tet:technology" {
    when '../../../../../../../../../../'
       + 'nw:network-types/tet:te-topology/'
       + 'wsont:wson-topology' {
      description
        "Augmentation parameters apply only for networks with
         WSON topology type.";
    }
    description
      "Augment TE label hop for the underlay primary path
       of the connectivity matrix entry.";
    case wson {
      uses l0-types:wson-label-hop;
    }
  }

  augment "/nw:networks/nw:network/nw:node/tet:te/"
        + "tet:te-node-attributes/tet:connectivity-matrices/"
        + "tet:connectivity-matrix/"
        + "tet:underlay/tet:backup-path/tet:path-element/"
        + "tet:type/tet:label/tet:label-hop/"
        + "tet:te-label/tet:technology" {
    when '../../../../../../../../../../'
       + 'nw:network-types/tet:te-topology/'
       + 'wsont:wson-topology' {
      description
        "Augmentation parameters apply only for networks with
         WSON topology type.";
    }
    description
      "Augment TE label hop for the underlay backup path
       of the connectivity matrix entry.";
    case wson {
      uses l0-types:wson-label-hop;
    }
  }

  augment "/nw:networks/nw:network/nw:node/tet:te/"
        + "tet:te-node-attributes/tet:connectivity-matrices/"
        + "tet:connectivity-matrix/tet:optimizations/"
        + "tet:algorithm/tet:metric/tet:optimization-metric/"
        + "tet:explicit-route-exclude-objects/"
        + "tet:route-object-exclude-object/tet:type/"
        + "tet:label/tet:label-hop/tet:te-label/tet:technology" {
    when '../../../../../../../../../../../'
       + 'nw:network-types/tet:te-topology/'
       + 'wsont:wson-topology' {
      description
        "Augmentation parameters apply only for networks with
         WSON topology type.";
    }
    description
      "Augment TE label hop for the explicit route objects excluded
       by the path computation of the connectivity matrix entry.";
    case wson {
      uses l0-types:wson-label-hop;
    }
  }

  augment "/nw:networks/nw:network/nw:node/tet:te/"
        + "tet:te-node-attributes/tet:connectivity-matrices/"
        + "tet:connectivity-matrix/tet:optimizations/"
        + "tet:algorithm/tet:metric/tet:optimization-metric/"
        + "tet:explicit-route-include-objects/"
        + "tet:route-object-include-object/tet:type/"
        + "tet:label/tet:label-hop/tet:te-label/tet:technology" {
    when '../../../../../../../../../../../'
       + 'nw:network-types/tet:te-topology/'
       + 'wsont:wson-topology' {
      description
        "Augmentation parameters apply only for networks with
         WSON topology type.";
    }
    description
      "Augment TE label hop for the explicit route objects included
       by the path computation of the connectivity matrix entry.";
    case wson {
      uses l0-types:wson-label-hop;
    }
  }

  augment "/nw:networks/nw:network/nw:node/tet:te/"
        + "tet:te-node-attributes/tet:connectivity-matrices/"
        + "tet:connectivity-matrix/"
        + "tet:path-properties/tet:path-route-objects/"
        + "tet:path-route-object/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the computed path route objects
       of the connectivity matrix entry.";
    case wson {
      uses l0-types:wson-label-hop;
    }
  }

  augment "/nw:networks/nw:network/nw:node/tet:te/"
        + "tet:information-source-entry/"
        + "tet:connectivity-matrices/tet:label-restrictions/"
        + "tet:label-restriction/"
        + "tet:label-start/tet:te-label/tet:technology" {
    when '../../../../../../../../'
       + 'nw:network-types/tet:te-topology/'
       + 'wsont:wson-topology' {
      description
        "Augmentation parameters apply only for networks with
         WSON topology type.";
    }
    description
      "Augment TE label range start for the TE node connectivity
       matrices information source.";
    case wson {
      uses l0-types:wson-label-start-end;
    }
  }

  augment "/nw:networks/nw:network/nw:node/tet:te/"
        + "tet:information-source-entry/"
        + "tet:connectivity-matrices/tet:label-restrictions/"
        + "tet:label-restriction/"
        + "tet:label-end/tet:te-label/tet:technology" {
    when '../../../../../../../../'
       + 'nw:network-types/tet:te-topology/'
       + 'wsont:wson-topology' {
      description
        "Augmentation parameters apply only for networks with
         WSON topology type.";
    }
    description
      "Augment TE label range end for the TE node connectivity
       matrices information source.";
    case wson {
      uses l0-types:wson-label-start-end;
    }
  }

  augment "/nw:networks/nw:network/nw:node/tet:te/"
        + "tet:information-source-entry/"
        + "tet:connectivity-matrices/tet:label-restrictions/"
        + "tet:label-restriction/"
        + "tet:label-step/tet:technology" {
    when '../../../../../../../'
       + 'nw:network-types/tet:te-topology/'
       + 'wsont:wson-topology' {
      description
        "Augmentation parameters apply only for networks with
         WSON topology type.";
    }
    description
      "Augment TE label range step for the TE node connectivity
       matrices information source.";
    case wson {
      uses l0-types:wson-label-step;
    }
  }

  augment "/nw:networks/nw:network/nw:node/tet:te/"
        + "tet:information-source-entry/tet:connectivity-matrices/"
        + "tet:underlay/tet:primary-path/tet:path-element/tet:type/"
        + "tet:label/tet:label-hop/tet:te-label/tet:technology" {
    when '../../../../../../../../../'
       + 'nw:network-types/tet:te-topology/'
       + 'wsont:wson-topology' {
      description
        "Augmentation parameters apply only for networks with
         WSON topology type.";
    }
    description
      "Augment TE label hop for the underlay primary path
       of the TE node connectivity matrices of the information
       source entry.";
    case wson {
      uses l0-types:wson-label-hop;
    }
  }

  augment "/nw:networks/nw:network/nw:node/tet:te/"
        + "tet:information-source-entry/tet:connectivity-matrices/"
        + "tet:underlay/tet:backup-path/tet:path-element/tet:type/"
        + "tet:label/tet:label-hop/tet:te-label/tet:technology" {
    when '../../../../../../../../../'
       + 'nw:network-types/tet:te-topology/'
       + 'wsont:wson-topology' {
      description
        "Augmentation parameters apply only for networks with
         WSON topology type.";
    }
    description
      "Augment TE label hop for the underlay backup path
       of the TE node connectivity matrices of the information
       source entry.";
    case wson {
      uses l0-types:wson-label-hop;
    }
  }

  augment "/nw:networks/nw:network/nw:node/tet:te/"
        + "tet:information-source-entry/tet:connectivity-matrices/"
        + "tet:optimizations/tet:algorithm/tet:metric/"
        + "tet:optimization-metric/"
        + "tet:explicit-route-exclude-objects/"
        + "tet:route-object-exclude-object/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the explicit route objects excluded
       by the path computation of the TE node connectivity matrices
       information source.";
    case wson {
      uses l0-types:wson-label-hop;
    }
  }

  augment "/nw:networks/nw:network/nw:node/tet:te/"
        + "tet:information-source-entry/tet:connectivity-matrices/"
        + "tet:optimizations/tet:algorithm/tet:metric/"
        + "tet:optimization-metric/"
        + "tet:explicit-route-include-objects/"
        + "tet:route-object-include-object/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the explicit route objects included
       by the path computation of the TE node connectivity matrices
       information source.";
    case wson {
      uses l0-types:wson-label-hop;
    }
  }

  augment "/nw:networks/nw:network/nw:node/tet:te/"
        + "tet:information-source-entry/tet:connectivity-matrices/"
        + "tet:path-properties/tet:path-route-objects/"
        + "tet:path-route-object/tet:type/"
        + "tet:label/tet:label-hop/tet:te-label/tet:technology" {
    when '../../../../../../../../../'
       + 'nw:network-types/tet:te-topology/'
       + 'wsont:wson-topology' {
      description
        "Augmentation parameters apply only for networks with
         WSON topology type.";
    }
    description
      "Augment TE label hop for the computed path route objects
       of the TE node connectivity matrices information source.";
    case wson {
      uses l0-types:wson-label-hop;
    }
  }

  augment "/nw:networks/nw:network/nw:node/tet:te/"
        + "tet:information-source-entry/tet:connectivity-matrices/"
        + "tet:connectivity-matrix/"
        + "tet:from/tet:label-restrictions/"
        + "tet:label-restriction/"
        + "tet:label-start/tet:te-label/tet:technology" {
    when '../../../../../../../../../../'
       + 'nw:network-types/tet:te-topology/'
       + 'wsont:wson-topology' {
      description
        "Augmentation parameters apply only for networks with
         WSON topology type.";
    }
    description
      "Augment TE label range start for the source LTP
       of the connectivity matrix entry information source.";
    case wson {
      uses l0-types:wson-label-start-end;
    }
  }
  augment "/nw:networks/nw:network/nw:node/tet:te/"
        + "tet:information-source-entry/tet:connectivity-matrices/"
        + "tet:connectivity-matrix/"
        + "tet:from/tet:label-restrictions/"
        + "tet:label-restriction/"
        + "tet:label-end/tet:te-label/tet:technology" {
    when '../../../../../../../../../../'
       + 'nw:network-types/tet:te-topology/'
       + 'wsont:wson-topology' {
      description
        "Augmentation parameters apply only for networks with
         WSON topology type.";
    }
    description
      "Augment TE label range end for the source LTP
       of the connectivity matrix entry information source.";
    case wson {
      uses l0-types:wson-label-start-end;
    }
  }

  augment "/nw:networks/nw:network/nw:node/tet:te/"
        + "tet:information-source-entry/tet:connectivity-matrices/"
        + "tet:connectivity-matrix/"
        + "tet:from/tet:label-restrictions/"
        + "tet:label-restriction/"
        + "tet:label-step/tet:technology" {
    when '../../../../../../../../../'
       + 'nw:network-types/tet:te-topology/'
       + 'wsont:wson-topology' {
      description
        "Augmentation parameters apply only for networks with
         WSON topology type.";
    }
    description
      "Augment TE label range step for the source LTP
       of the connectivity matrix entry information source.";
    case wson {
      uses l0-types:wson-label-step;
    }
  }

  augment "/nw:networks/nw:network/nw:node/tet:te/"
        + "tet:information-source-entry/tet:connectivity-matrices/"
        + "tet:connectivity-matrix/"
        + "tet:to/tet:label-restrictions/tet:label-restriction/"
        + "tet:label-start/tet:te-label/tet:technology" {
    when '../../../../../../../../../../'
       + 'nw:network-types/tet:te-topology/'
       + 'wsont:wson-topology' {
      description
        "Augmentation parameters apply only for networks with
         WSON topology type.";
    }
    description
      "Augment TE label range start for the destination LTP
       of the connectivity matrix entry information source.";
    case wson {
      uses l0-types:wson-label-start-end;
    }
  }

  augment "/nw:networks/nw:network/nw:node/tet:te/"
        + "tet:information-source-entry/tet:connectivity-matrices/"
        + "tet:connectivity-matrix/"
        + "tet:to/tet:label-restrictions/tet:label-restriction/"
        + "tet:label-end/tet:te-label/tet:technology" {
    when '../../../../../../../../../../'
       + 'nw:network-types/tet:te-topology/'
       + 'wsont:wson-topology' {
      description
        "Augmentation parameters apply only for networks with
         WSON topology type.";
    }
    description
      "Augment TE label range end for the destination LTP
       of the connectivity matrix entry information source.";
    case wson {
      uses l0-types:wson-label-start-end;
    }
  }

  augment "/nw:networks/nw:network/nw:node/tet:te/"
        + "tet:information-source-entry/tet:connectivity-matrices/"
        + "tet:connectivity-matrix/"
        + "tet:to/tet:label-restrictions/tet:label-restriction/"
        + "tet:label-step/tet:technology" {
    when '../../../../../../../../../'
       + 'nw:network-types/tet:te-topology/'
       + 'wsont:wson-topology' {
      description
        "Augmentation parameters apply only for networks with
         WSON topology type.";
    }
    description
      "Augment TE label range step for the destination LTP
       of the connectivity matrix entry information source.";
    case wson {
      uses l0-types:wson-label-step;
    }
  }

  augment "/nw:networks/nw:network/nw:node/tet:te/"
        + "tet:information-source-entry/tet:connectivity-matrices/"
        + "tet:connectivity-matrix/"
        + "tet:underlay/tet:primary-path/tet:path-element/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the underlay primary path
       of the connectivity matrix entry information source.";
    case wson {
      uses l0-types:wson-label-hop;
    }
  }

  augment "/nw:networks/nw:network/nw:node/tet:te/"
        + "tet:information-source-entry/tet:connectivity-matrices/"
        + "tet:connectivity-matrix/"
        + "tet:underlay/tet:backup-path/tet:path-element/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the underlay backup path
       of the connectivity matrix entry information source.";
    case wson {
      uses l0-types:wson-label-hop;
    }
  }

  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-exclude-objects/"
        + "tet:route-object-exclude-object/tet:type/"
        + "tet:label/tet:label-hop/tet:te-label/tet:technology" {
    when '../../../../../../../../../../../'
       + 'nw:network-types/tet:te-topology/'
       + 'wsont:wson-topology' {
      description
        "Augmentation parameters apply only for networks with
         WSON topology type.";
    }
    description
      "Augment TE label hop for the explicit route objects excluded
       by the path computation of the connectivity matrix entry
       information source.";
    case wson {
      uses l0-types:wson-label-hop;
    }
  }

  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-include-objects/"
        + "tet:route-object-include-object/tet:type/"
        + "tet:label/tet:label-hop/tet:te-label/tet:technology" {
    when '../../../../../../../../../../../'
       + 'nw:network-types/tet:te-topology/'
       + 'wsont:wson-topology' {
      description
        "Augmentation parameters apply only for networks with
         WSON topology type.";
    }
    description
      "Augment TE label hop for the explicit route objects included
       by the path computation of the connectivity matrix entry
       information source.";
    case wson {
      uses l0-types:wson-label-hop;
    }
  }

  augment "/nw:networks/nw:network/nw:node/tet:te/"
        + "tet:information-source-entry/tet:connectivity-matrices/"
        + "tet:connectivity-matrix/"
        + "tet:path-properties/tet:path-route-objects/"
        + "tet:path-route-object/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the computed path route objects
       of the connectivity matrix entry information source.";
    case wson {
      uses l0-types:wson-label-hop;
    }
  }

  augment "/nw:networks/nw:network/nw:node/tet:te/"
        + "tet:tunnel-termination-point/"
        + "tet:local-link-connectivities/"
        + "tet:label-restrictions/tet:label-restriction/"
        + "tet:label-start/"
        + "tet:te-label/tet:technology" {
    when '../../../../../../../../'
       + 'nw:network-types/tet:te-topology/'
       + 'wsont:wson-topology' {
      description
        "Augmentation parameters apply only for networks with
         WSON topology type.";
    }
    description
      "Augment TE label range start for the TTP
       Local Link Connectivities.";
    case wson {
      uses l0-types:wson-label-start-end;
    }
  }

  augment "/nw:networks/nw:network/nw:node/tet:te/"
        + "tet:tunnel-termination-point/"
        + "tet:local-link-connectivities/"
        + "tet:label-restrictions/tet:label-restriction/"
        + "tet:label-end/"
        + "tet:te-label/tet:technology" {
    when '../../../../../../../../'
       + 'nw:network-types/tet:te-topology/'
       + 'wsont:wson-topology' {
      description
        "Augmentation parameters apply only for networks with
         WSON topology type.";
    }
    description
      "Augment TE label range end for the TTP
       Local Link Connectivities.";
    case wson {
      uses l0-types:wson-label-start-end;
    }
  }

  augment "/nw:networks/nw:network/nw:node/tet:te/"
        + "tet:tunnel-termination-point/"
        + "tet:local-link-connectivities/"
        + "tet:label-restrictions/tet:label-restriction/"
        + "tet:label-step/"
        + "tet:technology" {
    when '../../../../../../../'
       + 'nw:network-types/tet:te-topology/'
       + 'wsont:wson-topology' {
      description
        "Augmentation parameters apply only for networks with
         WSON topology type.";
    }
    description
      "Augment TE label range step for the TTP
       Local Link Connectivities.";
    case wson {
      uses l0-types:wson-label-step;
    }
  }

  augment "/nw:networks/nw:network/nw:node/tet:te/"
        + "tet:tunnel-termination-point/"
        + "tet:local-link-connectivities/"
        + "tet:underlay/tet:primary-path/tet:path-element/tet:type/"
        + "tet:label/tet:label-hop/tet:te-label/tet:technology" {
    when '../../../../../../../../../'
       + 'nw:network-types/tet:te-topology/'
       + 'wsont:wson-topology' {
      description
        "Augmentation parameters apply only for networks with
         WSON topology type.";
    }
    description
      "Augment TE label hop for the underlay primary path
       of the TTP Local Link Connectivities.";
    case wson {
      uses l0-types:wson-label-hop;
    }
  }

  augment "/nw:networks/nw:network/nw:node/tet:te/"
        + "tet:tunnel-termination-point/"
        + "tet:local-link-connectivities/"
        + "tet:underlay/tet:backup-path/tet:path-element/tet:type/"
        + "tet:label/tet:label-hop/tet:te-label/tet:technology" {
    when '../../../../../../../../../'
       + 'nw:network-types/tet:te-topology/'
       + 'wsont:wson-topology' {
      description
        "Augmentation parameters apply only for networks with
         WSON topology type.";
    }
    description
      "Augment TE label hop for the underlay backup path
       of the TTP Local Link Connectivities.";
    case wson {
      uses l0-types:wson-label-hop;
    }
  }

  augment "/nw:networks/nw:network/nw:node/tet:te/"
        + "tet:tunnel-termination-point/"
        + "tet:local-link-connectivities/"
        + "tet:optimizations/tet:algorithm/tet:metric/"
        + "tet:optimization-metric/"
        + "tet:explicit-route-exclude-objects/"
        + "tet:route-object-exclude-object/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the explicit route objects excluded
       by the path computation of the TTP Local Link
       Connectivities.";
    case wson {
      uses l0-types:wson-label-hop;
    }
  }

  augment "/nw:networks/nw:network/nw:node/tet:te/"
        + "tet:tunnel-termination-point/"
        + "tet:local-link-connectivities/"
        + "tet:optimizations/tet:algorithm/tet:metric/"
        + "tet:optimization-metric/"
        + "tet:explicit-route-include-objects/"
        + "tet:route-object-include-object/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the explicit route objects included
       by the path computation of the TTP Local Link
       Connectivities.";
    case wson {
      uses l0-types:wson-label-hop;
    }
  }

  augment "/nw:networks/nw:network/nw:node/tet:te/"
        + "tet:tunnel-termination-point/"
        + "tet:local-link-connectivities/"
        + "tet:path-properties/tet:path-route-objects/"
        + "tet:path-route-object/tet:type/"
        + "tet:label/tet:label-hop/tet:te-label/tet:technology" {
    when '../../../../../../../../../'
       + 'nw:network-types/tet:te-topology/'
       + 'wsont:wson-topology' {
      description
        "Augmentation parameters apply only for networks with
         WSON topology type.";
    }
    description
      "Augment TE label hop for the computed path route objects
       of the TTP Local Link Connectivities.";
    case wson {
      uses l0-types:wson-label-hop;
    }
  }

  augment "/nw:networks/nw:network/nw:node/tet:te/"
        + "tet:tunnel-termination-point/"
        + "tet:local-link-connectivities/"
        + "tet:local-link-connectivity/"
        + "tet:label-restrictions/tet:label-restriction/"
        + "tet:label-start/tet:te-label/tet:technology" {
    when '../../../../../../../../../'
       + 'nw:network-types/tet:te-topology/'
       + 'wsont:wson-topology' {
      description
        "Augmentation parameters apply only for networks with
         WSON topology type.";
    }
    description
      "Augment TE label range start for the TTP
       Local Link Connectivity entry.";
    case wson {
      uses l0-types:wson-label-start-end;
    }
  }

  augment "/nw:networks/nw:network/nw:node/tet:te/"
        + "tet:tunnel-termination-point/"
        + "tet:local-link-connectivities/"
        + "tet:local-link-connectivity/"
        + "tet:label-restrictions/tet:label-restriction/"
        + "tet:label-end/tet:te-label/tet:technology" {
    when '../../../../../../../../../'
       + 'nw:network-types/tet:te-topology/'
       + 'wsont:wson-topology' {
      description
        "Augmentation parameters apply only for networks with
         WSON topology type.";
    }
    description
      "Augment TE label range end for the TTP
       Local Link Connectivity entry.";
    case wson {
      uses l0-types:wson-label-start-end;
    }
  }

  augment "/nw:networks/nw:network/nw:node/tet:te/"
        + "tet:tunnel-termination-point/"
        + "tet:local-link-connectivities/"
        + "tet:local-link-connectivity/"
        + "tet:label-restrictions/tet:label-restriction/"
        + "tet:label-step/tet:technology" {
    when '../../../../../../../../'
       + 'nw:network-types/tet:te-topology/'
       + 'wsont:wson-topology' {
      description
        "Augmentation parameters apply only for networks with
         WSON topology type.";
    }
    description
      "Augment TE label range step for the TTP
       Local Link Connectivity entry.";
    case wson {
      uses l0-types:wson-label-step;
    }
  }

  augment "/nw:networks/nw:network/nw:node/tet:te/"
        + "tet:tunnel-termination-point/"
        + "tet:local-link-connectivities/"
        + "tet:local-link-connectivity/"
        + "tet:underlay/tet:primary-path/tet:path-element/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the underlay primary path
       of the TTP Local Link Connectivity entry.";
    case wson {
      uses l0-types:wson-label-hop;
    }
  }

  augment "/nw:networks/nw:network/nw:node/tet:te/"
        + "tet:tunnel-termination-point/"
        + "tet:local-link-connectivities/"
        + "tet:local-link-connectivity/"
        + "tet:underlay/tet:backup-path/tet:path-element/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the underlay backup path
       of the TTP Local Link Connectivity entry.";
    case wson {
      uses l0-types:wson-label-hop;
    }
  }

  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-exclude-objects/"
        + "tet:route-object-exclude-object/tet:type/"
        + "tet:label/tet:label-hop/tet:te-label/tet:technology" {
    when '../../../../../../../../../../../'
       + 'nw:network-types/tet:te-topology/'
       + 'wsont:wson-topology' {
      description
        "Augmentation parameters apply only for networks with
         WSON topology type.";
    }
    description
      "Augment TE label hop for the explicit route objects excluded
       by the path computation of the TTP Local Link
       Connectivity entry.";
    case wson {
      uses l0-types:wson-label-hop;
    }
  }

  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-include-objects/"
        + "tet:route-object-include-object/tet:type/"
        + "tet:label/tet:label-hop/tet:te-label/tet:technology" {
    when '../../../../../../../../../../../'
       + 'nw:network-types/tet:te-topology/'
       + 'wsont:wson-topology' {
      description
        "Augmentation parameters apply only for networks with
         WSON topology type.";
    }
    description
      "Augment TE label hop for the explicit route objects included
       by the path computation of the TTP Local Link
       Connectivity entry.";
    case wson {
      uses l0-types:wson-label-hop;
    }
  }

  augment "/nw:networks/nw:network/nw:node/tet:te/"
        + "tet:tunnel-termination-point/"
        + "tet:local-link-connectivities/"
        + "tet:local-link-connectivity/"
        + "tet:path-properties/tet:path-route-objects/"
        + "tet:path-route-object/tet:type/"
        + "tet:label/tet:label-hop/tet:te-label/tet:technology" {
    when '../../../../../../../../../../'
       + 'nw:network-types/tet:te-topology/'
       + 'wsont:wson-topology' {
      description
        "Augmentation parameters apply only for networks with
         WSON topology type.";
    }
    description
      "Augment TE label hop for the computed path route objects
       of the TTP Local Link Connectivity entry.";
    case wson {
      uses l0-types:wson-label-hop;
    }
  }
  augment "/nw:networks/nw:network/nt:link/tet:te/"
        + "tet:te-link-attributes/"
        + "tet:underlay/tet:primary-path/tet:path-element/tet:type/"
        + "tet:label/tet:label-hop/tet:te-label/tet:technology" {
    when '../../../../../../../../'
       + 'nw:network-types/tet:te-topology/'
       + 'wsont:wson-topology' {
      description
        "Augmentation parameters apply only for networks with
         WSON topology type.";
    }
    description
      "Augment TE label hop for the underlay primary path
       of the TE link.";
    case wson {
      uses l0-types:wson-label-hop;
    }
  }

  augment "/nw:networks/nw:network/nt:link/tet:te/"
        + "tet:te-link-attributes/"
        + "tet:underlay/tet:backup-path/tet:path-element/tet:type/"
        + "tet:label/tet:label-hop/tet:te-label/tet:technology" {
    when '../../../../../../../../'
       + 'nw:network-types/tet:te-topology/'
       + 'wsont:wson-topology' {
      description
        "Augmentation parameters apply only for networks with
         WSON topology type.";
    }
    description
      "Augment TE label hop for the underlay backup path
       of the TE link.";
    case wson {
      uses l0-types:wson-label-hop;
    }
  }

  augment "/nw:networks/nw:network/nt:link/tet:te/"
        + "tet:te-link-attributes/"
        + "tet:label-restrictions/tet:label-restriction/"
        + "tet:label-start/tet:te-label/tet:technology" {
    when '../../../../../../../nw:network-types/tet:te-topology/'
       + 'wsont:wson-topology' {
      description
        "Augmentation parameters apply only for networks with
         WSON topology type.";
    }
    description
      "Augment TE label range start for the TE link.";
    case wson {
      uses l0-types:wson-label-start-end;
    }
  }

  augment "/nw:networks/nw:network/nt:link/tet:te/"
        + "tet:te-link-attributes/"
        + "tet:label-restrictions/tet:label-restriction/"
        + "tet:label-end/tet:te-label/tet:technology" {
    when '../../../../../../../nw:network-types/tet:te-topology/'
       + 'wsont:wson-topology' {
      description
        "Augmentation parameters apply only for networks with
         WSON topology type.";
    }
    description
      "Augment TE label range end for the TE link.";
    case wson {
      uses l0-types:wson-label-start-end;
    }
  }

  augment "/nw:networks/nw:network/nt:link/tet:te/"
        + "tet:te-link-attributes/"
        + "tet:label-restrictions/tet:label-restriction/"
        + "tet:label-step/tet:technology" {
    when '../../../../../../nw:network-types/tet:te-topology/'
       + 'wsont:wson-topology' {
      description
        "Augmentation parameters apply only for networks with
         WSON topology type.";
    }
    description
      "Augment TE label range step for the TE link.";
    case wson {
      uses l0-types:wson-label-step;
    }
  }

  augment "/nw:networks/nw:network/nt:link/tet:te/"
        + "tet:information-source-entry/"
        + "tet:label-restrictions/tet:label-restriction/"
        + "tet:label-start/tet:te-label/tet:technology" {
    when '../../../../../../../nw:network-types/tet:te-topology/'
       + 'wsont:wson-topology' {
      description
        "Augmentation parameters apply only for networks with
         WSON topology type.";
    }
    description
      "Augment TE label range start for the TE link
       information source.";
    case wson {
      uses l0-types:wson-label-start-end;
    }
  }

  augment "/nw:networks/nw:network/nt:link/tet:te/"
        + "tet:information-source-entry/"
        + "tet:label-restrictions/tet:label-restriction/"
        + "tet:label-end/tet:te-label/tet:technology" {
    when '../../../../../../../nw:network-types/tet:te-topology/'
       + 'wsont:wson-topology' {
      description
        "Augmentation parameters apply only for networks with
         WSON topology type.";
    }
    description
      "Augment TE label range end for the TE link
       information source.";
    case wson {
      uses l0-types:wson-label-start-end;
    }
  }

  augment "/nw:networks/nw:network/nt:link/tet:te/"
        + "tet:information-source-entry/"
        + "tet:label-restrictions/tet:label-restriction/"
        + "tet:label-step/tet:technology" {
    when '../../../../../../nw:network-types/tet:te-topology/'
       + 'wsont:wson-topology' {
      description
        "Augmentation parameters apply only for networks with
         WSON topology type.";
    }
    description
      "Augment TE label range step for the TE link
       information source.";
    case wson {
      uses l0-types:wson-label-step;
    }
  }

  augment "/nw:networks/tet:te/tet:templates/"
        + "tet:link-template/tet:te-link-attributes/"
        + "tet:underlay/tet:primary-path/tet:path-element/tet:type/"
        + "tet:label/tet:label-hop/tet:te-label/tet:technology" {
    description
      "Augment TE label hop for the underlay primary path
       of the TE link template.";
    case wson {
      uses l0-types:wson-label-hop;
    }
  }

  augment "/nw:networks/tet:te/tet:templates/"
        + "tet:link-template/tet:te-link-attributes/"
        + "tet:underlay/tet:backup-path/tet:path-element/tet:type/"
        + "tet:label/tet:label-hop/tet:te-label/tet:technology" {
    description
      "Augment TE label hop for the underlay backup path
       of the TE link template.";
    case wson {
      uses l0-types:wson-label-hop;
    }
  }

  augment "/nw:networks/tet:te/tet:templates/"
        + "tet:link-template/tet:te-link-attributes/"
        + "tet:label-restrictions/tet:label-restriction/"
        + "tet:label-start/tet:te-label/tet:technology" {
    description
      "Augment TE label range start for the TE link template.";
    case wson {
      uses l0-types:wson-label-start-end;
    }
  }

  augment "/nw:networks/tet:te/tet:templates/"
        + "tet:link-template/tet:te-link-attributes/"
        + "tet:label-restrictions/tet:label-restriction/"
        + "tet:label-end/tet:te-label/tet:technology" {
    description
      "Augment TE label range end for the TE link template.";
    case wson {
      uses l0-types:wson-label-start-end;
    }
  }

  augment "/nw:networks/tet:te/tet:templates/"
        + "tet:link-template/tet:te-link-attributes/"
        + "tet:label-restrictions/tet:label-restriction/"
        + "tet:label-step/tet:technology" {
    description
      "Augment TE label range step for the TE link template.";
    case wson {
      uses l0-types:wson-label-step;
    }
  }
}
